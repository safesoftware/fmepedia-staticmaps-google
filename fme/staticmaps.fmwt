FME workspace staticmaps.fmwt
Title: staticmaps
Description: This sample shows how to generate maps with FME using the Google Static Maps API with points and polygons drawn on top.
Google provides the Static Map API, which is a simple tool to get a static map (JPG) of a desired region. In this example, users send request parameters to FME Server using a simple HTML form and receive their result in an email.
Usage: Setup
    Save this template in a directory. Additional files are saved in a sub directory. 
    Create a new topic 'staticmap_report' 
    Assign this topic to a configured email subscription (http://fmepedia.safe.com/articles/How_To/Email-Configuration-for-FME-Server) 
    Adapt the FMEServerNotifier in the workspace. 
    Publish the workspace as a JobSubmitter to FME Server (adapt the FMEServerNotifier URL, Username and PW) 
    Adapt the URL from the action attribute (form tag, line 24) in the index.html file 
    Copy all content of the web folder to a webserver, or open the index.html file in a web browser
Requirements: FME 2013
History: 2012-10-10,Claude Vessaz,Created
Legal terms conditions: Copyright (c) 2012 Safe Software Inc.
Permission is granted to anyone, free of charge, to use, modify and distribute the object code form of this template for any purpose, subject to the following restrictions:
1) The origin of this template and associated FME(R) software must not be misrepresented.
2) This template may only be used in conjunction with a validly licensed copy of FME software.
THIS SOFTWARE IS PROVIDED BY SAFE SOFTWARE INC. "AS IS" AND ANY EXPRESS OR IMPLIED WARRANTIES, INCLUDING, BUT NOT LIMITED TO, THE IMPLIED WARRANTIES OF MERCHANTABILITY, NONINFRINGEMENT AND FITNESS FOR A PARTICULAR PURPOSE ARE DISCLAIMED. IN NO EVENT SHALL SAFE SOFTWARE INC. BE LIABLE FOR ANY DIRECT, INDIRECT, INCIDENTAL, SPECIAL, EXEMPLARY, OR CONSEQUENTIAL DAMAGES (INCLUDING, BUT NOT LIMITED TO, PROCUREMENT OF SUBSTITUTE GOODS OR SERVICES; LOSS OF USE, DATA, OR PROFITS; OR BUSINESS INTERRUPTION) HOWEVER CAUSED AND ON ANY THEORY OF LIABILITY, WHETHER IN CONTRACT, STRICT LIABILITY, OR TORT (INCLUDING NEGLIGENCE OR OTHERWISE) ARISING IN ANY WAY OUT OF THE USE OF THIS SOFTWARE, EVEN IF ADVISED OF THE POSSIBILITY OF SUCH DAMAGE.

Parameters:
- park_name = Big Walnut Creek   # Park Name
- email = amun.dhak@safe.com   # User email address
- geometry = false   # Geometry
- URL = http://fmepedia2014-safe-software.fmecloud.com   # Web Connection URL
- HTTP_AUTH_USERNAME = fmepediademos   # Username
- HTTP_AUTH_PASSWORD =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   # Password

Readers:
- MITAB_1: MITAB from $(FME_MF_DIR)1/Parks/city_parks.tab

city_parks (reader MITAB_1)
    attributes: name char(64), name_alt char(64)
    -> TestFilter
Note: Filter parks
TestFilter
    TEST_LIST = BOOL_OP,OR,COMPOSITE_TEST,<Unused>,TEST_CLAUSE,"TEST ""@Value(name)"" = ""$(park_name)""",Park Name
    DEFAULT_VALUE = <UNFILTERED>
    Park Name -> Reprojector
Note: Google Maps uses the WGS84 / coordinate system
Reprojector
    DEST = EPSG:4326
    RASTER_CELL_SIZE = Preserve Cells
    STROKE_ARCS = Yes
    SOURCE = TX83-CF
    INTERPOLATION_TYPE_NAME = Nearest Neighbor
    REPROJECTED -> TestFilter_2
TestFilter_2
    TEST_LIST = BOOL_OP,OR,COMPOSITE_TEST,<Unused>,TEST_CLAUSE,"TEST ""$(geometry)"" = ""false""",geometry = false,BOOL_OP,OR,COMPOSITE_TEST,<Unused>,TEST_CLAUSE,"TEST ""$(geometry)"" = ""true""",geometry = true
    DEFAULT_VALUE = <UNFILTERED>
    geometry = true -> GeometryExtractor
    geometry = false -> CenterPointReplacer
CenterPointReplacer
    CENTERPOINT -> CoordinateExtractor
Note: Extract centerpoint coordinates
Note: https://developers.google.com/maps/documentation/staticmaps/
CoordinateExtractor
    Y_ATTR = _y
    X_ATTR = _x
    Z_DEFAULT = -9999
    Z_ATTR = _z
    IND = 0
    -> AttributeCreator
Note: Extract park geometry and convert / to an encoded polyline
GeometryExtractor
    ATTR = _geometry
    LEVELS_ATTR = _levels
    KIND_LONG = Encoded Polyline
    -> AttributeCreator_2
Note: Send the request to the / Google server
HTTPFetcher
    VAL_ATTR = staticmapimage
    USE_HEADER_ENCODING = No
    USE_COOKIES = No
    STATUS_CODE_ATTR = _http_status_code
    SAVED_HEADERS_ATTR = _headers
    HTTP_AUTH_METHOD = Basic
    URL = @Value(_StaticMapUrl)
    CONTINUE_ON_ERROR = No
    HTTP_PROXY_AUTH_METHOD = Basic
    -> StringConcatenator_3

Bookmark: Set map parameters
AttributeCreator
    ATTR_LIST = size,640,zoom,12
    -> StringConcatenator_5
AttributeCreator_2
    ATTR_LIST = size,640,path_weight,3,path_color,green,fillcolor,0x1A960933
    -> StringConcatenator_2

Bookmark: Set request URL
StringConcatenator_5
    PARM_LINE = http://maps.googleapis.com/maps/api/staticmap?center=@Value(_y),@Value(_x)&size=@Value(size)x@Value(size)&zoom=@Value(zoom)&sensor=false
    VAL_ATTR = _StaticMapUrl
    -> HTTPFetcher
StringConcatenator_2
    PARM_LINE = http://maps.googleapis.com/maps/api/staticmap?size=@Value(size)x@Value(size)&path=weight:@Value(path_weight)|color:@Value(path_color)|fillcolor:@Value(fillcolor)|enc:@Value(_geometry)&sensor=false
    VAL_ATTR = _StaticMapUrl
    -> HTTPFetcher

Bookmark: Write the received map to the disk
StringConcatenator_3
    PARM_LINE = $(FME_DATA_REPOSITORY)@Value(name).jpg
    VAL_ATTR = filename
    -> AttributeFileWriter
AttributeFileWriter
    CHAR_ENCODING = fme-system
    FILE_NAME = @Value(filename)
    SOURCE_ATTR = staticmapimage
    -> StringConcatenator

Bookmark: Send Confirmation Email
StringConcatenator
    PARM_LINE:
      {
      "email_to": "$(email)",
      "email_subject": "Your map of the @Value(name) park",
      "email_attachment": "@Value(filename)",
      "subscriber_content": "Your static map was successfully created"
      }
    VAL_ATTR = notify_content
    -> FMEServerNotifier
FMEServerNotifier
    HTTP_UPLOAD_BODY = notify_content
    HTTP_AUTH_PASSWORD = $(HTTP_AUTH_PASSWORD)
    STATUS_CODE_ATTR = _http_status_code
    TOPIC = staticmap_report
    HTTP_AUTH_USERNAME = $(HTTP_AUTH_USERNAME)
    URL = $(URL)
